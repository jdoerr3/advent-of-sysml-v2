package Day1_CristmasTree {

    part myChristmasTree {
        part trunk;
        part branches [5..10];
        part needles;
        part ornaments;
        part lights [100];
        part base;
    }
}
