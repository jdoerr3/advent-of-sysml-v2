package L04_SantaCargoBay_Challenge {
    part def Sleigh {
        part cargoBay {
            item payload : Bag;
        }
    }

    part def Bag;

    // Extend the model below as follows:
    // - Define the bottomless gift bag that can hold any number of gifts (gifts are items).
    // - Model Santa’s sleigh as a special kind of sleigh.
    // - In this sleigh, the cargo bay’s payload should be called a gift bag.
    // - The gift bag should always be a bottomless gift bag.
    // - The gift bag should contain at least a toy train, a teddy bear, and a candy cane.

    part def bottomlessBag :> Bag {
        item gifts : Gift [0..*];
    }

    item def Gift;

    part def santaSleigh :> Sleigh {
        part :>> cargoBay {
            item giftBag :>> payload : bottomlessBag {
                item 'toy train' :> gifts;
                item 'teddy bear' :> gifts;
                item 'candy cane' :> gifts;
            }
        }
    }
}
